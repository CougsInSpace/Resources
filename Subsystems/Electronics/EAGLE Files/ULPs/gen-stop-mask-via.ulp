#usage "<b>Generate an individual Solder Stop Mask for Vias.</b>\n"
       "<p>"
       "First set the <i>Limit</i> value in the Design Rule's <i>Mask</i> tab to the maximum "
       "drill diameter that is used for vias in your layout in order to avoid "
       "automatically generated solder stop symbols and RUN this ULP.<br> "
       "The ULP allows you to define a range of via drill diameters for which the solder stop "
       "mask should be defined. You could start the ULP several times to have different "
       "restring settings for vias with different drill diameters. <br>"
       "Usage: RUN gen-stop-mask-via "
       "<p> "
       "You can also delete the objects (Circle) generated by this ULP in the layers tStop "
       "or bStop afterwards, hide all layers except the layers t/bStop and use GROUP "
       "and DELETE (right mouse button)."
       "<p>"
       "<author>Author: support@cadsoft.de</author><br>"

// THIS PROGRAM IS PROVIDED AS IS AND WITHOUT WARRANTY OF ANY KIND, EXPRESSED OR IMPLIED
//
//
string Version = "1.0.0 2005-12-08";

real Trestring = 0.05;
real Brestring = 0.05;
real minDrill  = 0.1;
real maxDrill  = 1.0;
int  TStop = 1, BStop = 1;
int  CheckSetFlag = 0;

string h;
string cmd = "GRID mm;\n";

void draw_mask( int x, int y, real radius, int Layer) {
    sprintf(h, "CHANGE LAYER %d;\nCIRCLE 0 (%.3f %.3f) (%.3f %.3f);\n",
                Layer,  u2mm(x), u2mm(y), u2mm(x) + radius, u2mm(y) );
    cmd += h;
  return;
}

void  gen_mask( int x, int y, real Drill, int flag, int Layer) {
  real radius;
  if(!CheckSetFlag && (flag && VIA_FLAG_STOP)) return;
  if(CheckSetFlag == 1) {
    sprintf(h, "CHANGE STOP OFF (%.3f %.3f);\n", u2mm(x), u2mm(y));
    cmd += h;
  } 
  if (Layer == 1) {
    radius = Drill/2 + Trestring;
    draw_mask( x, y, radius, 29);
  }
  if (Layer == 16) {
    radius = Drill/2 + Brestring;
    draw_mask( x, y, radius, 30);
  }
  return;
}


if (board) board(B) {
  int Result = dlgDialog("Generate Stop Mask for Vias") {
    dlgLabel("<b><font color=\"red\">Set the <i>Limit</i> value in the Design Rule's Masks tab to maximum drill diameter</font></b>");
    dlgSpacing(8);
    dlgLabel("Via Drill Diameter Range [mm]");
    dlgHBoxLayout {
      dlgLabel("&min ");
      dlgRealEdit(minDrill, 0, 13.0);
      dlgLabel("&max ");
      dlgRealEdit(maxDrill, 0, 13.0);
      dlgStretch(1);
    }
    dlgHBoxLayout {
      dlgCheckBox("Generate tStop mask", TStop);
      dlgLabel("Mask Restring [mm]");
      dlgRealEdit(Trestring, 0, 5.0);
      dlgStretch(1);
    }
    dlgHBoxLayout {
      dlgCheckBox("Generate bStop mask", BStop);
      dlgLabel("Mask Restring [mm]");
      dlgRealEdit(Brestring, 0, 5.0);
      dlgStretch(1);
    }

    dlgHBoxLayout {
      dlgGroup("Solder Stop flag (CHANGE STOP ON|OFF)") {
        dlgRadioButton("Check Stop flag and generate mask for all with STOP OFF", CheckSetFlag);
        dlgRadioButton("Set Stop flag OFF for all and generate mask", CheckSetFlag);
        dlgRadioButton("Don't care about the flag, generate for all", CheckSetFlag);
        dlgRadioButton("Delete generated mask in t/bStop", CheckSetFlag);
      }
      dlgStretch(1);
    }
    dlgLabel("Version:" + Version);
    dlgHBoxLayout {
      dlgPushButton("+&OK") dlgAccept();
      dlgPushButton("-&Cancel") dlgReject();
      dlgStretch(1);
      dlgPushButton("&Help") dlgMessageBox(usage, "OK");
    }
  };
  if (!Result) exit (0);
  if (CheckSetFlag == 3) {
    if (TStop) {
      sprintf(h, "DISPLAY NONE 29;\n");
      cmd += h;
      B.circles(C) {
        if (C.layer == 29 && C.width == 0) {
          sprintf(h, "DELETE (%.3f %.3f);\n", u2mm(C.x), u2mm(C.y));
          cmd += h;
        }
      }
    }
    if (BStop) {
      sprintf(h, "DISPLAY NONE 30;\n");
      cmd += h;
      B.circles(C) {
        if (C.layer == 30 && C.width == 0) {
          sprintf(h, "DELETE (%.3f %.3f);\n", u2mm(C.x), u2mm(C.y));
          cmd += h;
        }
      }
    }
    sprintf(h, "DISPLAY NONE 1 16 18 29 30;\n");
    cmd += h;
  }
  else {
    sprintf(cmd, "DISPLAY NONE 1 16 18;\n");
    B.signals(S) {
      S.vias(V) {
        real Drill = u2mm(V.drill);
        if (Drill >= minDrill && Drill <= maxDrill) {
          if (V.start == 1 && TStop) gen_mask( V.x, V.y, Drill, V.flags, 1);
          if (V.end == 16  && BStop) gen_mask( V.x, V.y, Drill, V.flags, 16);
        }
      }
    }
  }
  exit (cmd);
}

else dlgMessageBox("Start this ULP in a Board!", "OK");
exit (0);
